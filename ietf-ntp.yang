module ietf-ntp {

  yang-version 1.1;

  namespace "urn:ietf:params:xml:ns:yang:ietf-ntp";

  prefix "ntp";

  import ietf-yang-types {
    prefix "yang";
    reference "RFC 6991: Common YANG Data Types";
  }

  import ietf-inet-types {
    prefix "inet";
    reference "RFC 6991: Common YANG Data Types";
  }

  import ietf-interfaces {
    prefix "if";
    reference "RFC 8343: A YANG Data Model for Interface Management";
  }

  import iana-crypt-hash {
    prefix "ianach";
    reference "RFC 7317: A YANG Data Model for System Management";
  }

  import ietf-key-chain {
    prefix "key-chain";
    reference "RFC 8177: YANG Data Model for Key Chains";
  }

  import ietf-access-control-list {
    prefix "acl";
    reference "RFC 8519: YANG Data Model for Network Access Control 
               Lists (ACLs)";
  }

  import ietf-routing-types {
    prefix "rt-types";
    reference "RFC 8294: Common YANG Data Types for the Routing Area";

  }

  import ietf-netconf-acm {
    prefix nacm;
    reference
      "RFC 8341: Network Configuration Protocol (NETCONF) Access
       Control Model";
  }

  organization
    "IETF NTP (Network Time Protocol) Working Group";

  contact
    "WG Web:  <http://tools.ietf.org/wg/ntp/>
    WG List:  <mailto: ntpwg@lists.ntp.org
    Editor:   Eric Wu
              <mailto:eric.wu@huawei.com>
    Editor:   Anil Kumar S N
              <mailto:anil.ietf@gmail.com>
    Editor:   Yi Zhao
              <mailto:yi.z.zhao@ericsson.com>
    Editor:   Dhruv Dhody
              <mailto:dhruv.ietf@gmail.com>
    Editor:   Ankit Kumar Sinha
              <mailto:ankit.ietf@gmail.com>";
  description
    "This document defines a YANG data model for Network Time Protocol
    (NTP) implementations. The data model includes configuration data 
    and state data.

    Copyright (c) 2019 IETF Trust and the persons identified
    as authors of the code. All rights reserved.

    Redistribution and use in source and binary forms,
    with or without modification, is permitted pursuant to,
    and subject to the license terms contained in, the
    Simplified BSD License set forth in Section 4.c of the
    IETF Trust's Legal Provisions Relating to IETF Documents
    (https://trustee.ietf.org/license-info).

    This version of this YANG module is part of RFC XXXX;
    see the RFC itself for full legal notices.";

  revision 2019-06-28 {
    description
      "Initial revision.";
    reference
      "RFC XXXX: A YANG Data Model for NTP.";
  }

  /* Note: The RFC Editor will replace XXXX with the number assigned  
  to this document once it becomes an RFC.*/

  /* Typedef Definitions */

  typedef ntp-stratum {
    type uint8 {
      range "1..16";
    }
    description
      "The level of each server in the hierarchy is defined by
      a stratum. Primary servers are assigned with stratum
      one; secondary servers at each lower level are assigned with
      one stratum greater than the preceding level";
    reference
      "RFC 5905: Network Time Protocol Version 4: Protocol and 
      Algorithms Specification";  
  }

  typedef ntp-version {
    type uint8; 
    default "3";
    description
      "The current NTP version supported by corresponding
      association.";
  }

  typedef ntp-minpoll {
    type uint8 {
      range "4..17";
    }
    default "6";
    description
      "The minimum poll exponent for this NTP association.";
    reference
      "RFC 5905: Network Time Protocol Version 4: Protocol and 
      Algorithms Specification";  
  }

  typedef ntp-maxpoll {
    type uint8 {
      range "4..17";
    }
    default "10";
    description
      "The maximum poll exponent for this NTP association.";
    reference
      "RFC 5905: Network Time Protocol Version 4: Protocol and 
      Algorithms Specification";  
  }

  typedef access-mode {
    type enumeration {
      enum peer {
        value "0";
        description
          "Enables the full access authority. Both time
          request and control query can be performed
          on the local NTP service, and the local clock
          can be synchronized with the remote server.";
      }
      enum server {
        value "1";
        description
          "Enables the server access and query.
          Both time requests and control query can be
          performed on the local NTP service, but the
          local clock cannot be synchronized with the
          remote server.";
      }
      enum synchronization {
        value "2";
        description
          "Enables the server to access.
          Only time request can be performed on the
          local NTP service.";
      }
      enum query {
        value "3";
        description
          "Enables the maximum access limitation.
          Control query can be performed only on the
          local NTP service.";
      }
    }
    description
      "This defines NTP access modes.";
  }

  typedef unicast-configuration-type {
    type enumeration {
      enum server {
        value "0";
        description
          "Use client association mode. This device
          will not provide synchronization to the
          configured NTP server.";
      }
      enum peer {
        value "1";
        description
          "Use symmetric active association mode.
          This device may provide synchronization
          to the configured NTP server.";
      }
    }
    description
      "This defines NTP unicast mode of operation.";
  }
  typedef association-mode {
    type enumeration {
      enum client {
        value "0";
        description
          "Use client association mode(mode 3).
          This device will not provide synchronization
          to the configured NTP server.";
      }
      enum active {
        value "1";
        description
          "Use symmetric active association mode(mode 1).
          This device may synchronize with its NTP peer,
          or provide synchronization to configured NTP peer.";
      }
      enum passive {
        value "2";
        description
          "Use symmetric passive association mode(mode 2).
          This device has learned this association dynamically.
          This device may synchronize with its NTP peer.";
      }
      enum broadcast {
        value "3";
        description
          "Use broadcast mode(mode 5).
          This mode defines that its either working
          as broadcast-server or multicast-server.";
      }
      enum broadcast-client {
        value "4";
        description
          "This mode defines that its either working
          as broadcast-client or multicast-client.";
      }
    }
    description
      "The NTP association modes.";
  }

  typedef ntp-clock-status {
    type enumeration {
      enum synchronized {
        value "0";
        description
          "Indicates that the local clock has been
          synchronized with an NTP server or
          the reference clock.";
      }
      enum unsynchronized {
        value "1";
        description
          "Indicates that the local clock has not been
          synchronized with any NTP server.";
      }
    }
    description
      "This defines NTP clock status.";
  }

  typedef ntp-sync-state {
    type enumeration {
      enum clock-not-set {
        value "0";
        description
          "Indicates the clock is not updated.";
      }
      enum freq-set-by-cfg {
        value "1";
        description
          "Indicates the clock frequency is set by
          NTP configuration.";
      }
      enum clock-set {
        value "2";
        description
          "Indicates the clock is set.";
      }
      enum freq-not-determined {
        value "3";
        description
          "Indicates the clock is set but the frequency
          is not determined.";
      }
      enum clock-synchronized {
        value "4";
        description
          "Indicates that the clock is synchronized";
      }
      enum spike {
        value "5";
        description
          "Indicates a time difference of more than 128
          milliseconds is detected between NTP server
          and client clock. The clock change will take
          effect in XXX seconds.";
      }
    }
    description
      "This defines NTP clock sync states.";
  }

  /* features */
  feature ntp-port {
    description
      "Support for NTP port configuration";
    reference 
      "RFC 5905: Network Time Protocol Version 4: Protocol and 
      Algorithms Specification";  
  }

  feature authentication {
    description
      "Support for NTP symmetric key authentication";
    reference 
      "RFC 5905: Network Time Protocol Version 4: Protocol and 
      Algorithms Specification";  
  }

  feature access-rules {
    description
      "Support for NTP access control";
    reference 
      "RFC 5905: Network Time Protocol Version 4: Protocol and 
      Algorithms Specification";  
  }

  feature unicast-configuration {
    description
      "Support for NTP client/server or active/passive
      in unicast";
    reference 
      "RFC 5905: Network Time Protocol Version 4: Protocol and 
      Algorithms Specification";  
  }

  feature broadcast-server {
    description
      "Support for broadcast server";
    reference 
      "RFC 5905: Network Time Protocol Version 4: Protocol and 
      Algorithms Specification";  
  }

  feature broadcast-client {
    description
      "Support for broadcast client";
    reference 
      "RFC 5905: Network Time Protocol Version 4: Protocol and 
      Algorithms Specification";  
  }

  feature multicast-server {
    description
      "Support for multicast server";
    reference 
      "RFC 5905: Network Time Protocol Version 4: Protocol and 
      Algorithms Specification";  
  }

  feature multicast-client {
    description
      "Support for multicast client";
    reference 
      "RFC 5905: Network Time Protocol Version 4: Protocol and 
      Algorithms Specification";  
  }

  feature manycast-server {
    description
      "Support for manycast server";
    reference 
      "RFC 5905: Network Time Protocol Version 4: Protocol and 
      Algorithms Specification";  
  }

  feature manycast-client {
    description
      "Support for manycast client";
    reference 
      "RFC 5905: Network Time Protocol Version 4: Protocol and 
      Algorithms Specification";  

  }

  /* Groupings */
  grouping authentication-key {
    description
      "To define an authentication key for a Network Time
      Protocol (NTP) time source.";
    leaf key-id {
      type uint32 {
        range "1..max";
      }
      description
        "Authentication key identifier.";
    }
    leaf algorithm {
      type identityref {
        base key-chain:crypto-algorithm;
      }
      description
        "Authentication algorithm.";
    }
    leaf key {
      nacm:default-deny-all;
      type ianach:crypt-hash;
      description
        "The key";
    }
    leaf istrusted {
      type boolean;
      description
        "Key-id is trusted or not";
    }
    reference 
      "RFC 5905: Network Time Protocol Version 4: Protocol and 
      Algorithms Specification";  
  }

  grouping authentication {
    description
      "Authentication.";
    choice authentication-type {
      description
        "Type of authentication.";
      case symmetric-key {
        leaf key-id {
          type leafref {
            path "/ntp:ntp/ntp:authentication/"
            + "ntp:authentication-keys/ntp:key-id";
          }
          description
            "Authentication key id referenced in this
            association.";
        }
      }
    }
  }

  grouping statistics {
    description
      "NTP packet statistic.";
    leaf packet-sent {
      type yang:counter32;
      description
        "The total number of NTP packets delivered to the
        transport service by this NTP entity for this
        association.
        Discountinuities in the value of this counter can occur
        upon cold start or reinitialization of the NTP entity, the
        management system and at other times as indicated by
        discontinuities in the value of sysUpTime.";
    }
    leaf packet-sent-fail {
      type yang:counter32;
      description
        "The number of times NTP packets sending failed.";
    }
    leaf packet-received {
      type yang:counter32;
      description
        "The total number of NTP packets delivered to the
        NTP entity from this association.
        Discountinuities in the value of this counter can occur
        upon cold start or reinitialization of the NTP entity, the
        management system and at other times as indicated by
        discontinuities in the value of sysUpTime.";
    }
    leaf packet-dropped {
      type yang:counter32;
      description
        "The total number of NTP packets that were delivered
        to this NTP entity from this association and this entity
        was not able to process due to an NTP protocol error.
        Discountinuities in the value of this counter can occur
        upon cold start or reinitialization of the NTP entity, the
        management system and at other times as indicated by
        discontinuities in the value of sysUpTime.";
    }
  }

  grouping common-attributes {
    description
      "NTP common attributes for configuration.";
    leaf minpoll {
      type ntp-minpoll;
      description
        "The minimum poll interval used in this association.";
    }
    leaf maxpoll {
      type ntp-maxpoll;
      description
        "The maximum poll interval used in this association.";
    }
    leaf port {
      if-feature ntp-port;
      type inet:port-number {
        range "123 | 1025..max";
      }
      default "123";
      description
        "Specify the port used to send NTP packets.";
    }
    leaf version {
      type ntp-version;
      description
        "NTP version.";
    }
    reference 
      "RFC 5905: Network Time Protocol Version 4: Protocol and 
      Algorithms Specification";  

  }

  grouping association-ref {
    description
      "Reference to NTP association mode";
    leaf associations-address {
      type leafref {
        path "/ntp:ntp/ntp:associations/ntp:address";
      }
      description
        "Indicates the association's address
        which result in clock synchronization.";
    }
    leaf associations-local-mode {
      type leafref {
        path "/ntp:ntp/ntp:associations/ntp:local-mode";
      }
      description
        "Indicates the association's local-mode
        which result in clock synchronization.";
    }
    leaf associations-isconfigured {
      type leafref {
        path "/ntp:ntp/ntp:associations/"
        + "ntp:isconfigured";
      }
      description
        "The association was configured or dynamic 
        which result in clock synchronization.";
    }
  }

  /* Configuration data nodes */
  container ntp {
    presence
      "NTP is enabled and system should attempt to
      synchronize the system clock with an NTP server
      from the 'ntp/associations' list.";
    description
      "Configuration parameters for NTP.";
    leaf port {
      if-feature ntp-port;
      type inet:port-number {
        range "123 | 1025..max";
      }
      default "123";
      description
        "Specify the port used to send and receive NTP packets.";
    }
    container refclock-master {
      presence
        "NTP master clock is enabled.";
      description
        "Configures the local clock of this device as NTP server.";
      leaf master-stratum {
        type ntp-stratum;
        default "16";
        description
          "Stratum level from which NTP
          clients get their time synchronized.";
      }
    }
    container authentication {
      description
        "Configuration of authentication.";
      leaf auth-enabled {
        type boolean;
        default false;
        description
          "Controls whether NTP authentication is enabled
          or disabled on this device.";
      }
      list authentication-keys {
        key "key-id";
        uses authentication-key;
        description
          "List of authentication keys.";
      }
    }

    container access-rules {
      description
        "Configuration to control access to NTP service 
        by using NTP access-group feature.
        The access-mode identifies how the acl is 
        applied with NTP.";
      list access-rule {
        key "access-mode";
        description
          "List of access rules.";
        leaf access-mode {
          type access-mode;
          description
            "NTP access mode. The defination of each possible values:
            peer(0): Both time request and control query can be 
            performed.
            server(1): Enables the server access and query.
            synchronization(2): Enables the server access only.
            query(3): Enables control query only.";
        }
        leaf acl {
          type leafref {
            path "/acl:acls/acl:acl/acl:name";
          }
          description
            "Control access configuration to be used.";
        }
        reference 
          "RFC 5905: Network Time Protocol Version 4: Protocol and 
          Algorithms Specification";  
      }
    }

    container clock-state {
      config "false";
      description
        "Clock operational state of the NTP.";

      container system-status {
        description
          "System status of NTP.";
        leaf clock-state {
          type ntp-clock-status;
          mandatory true;
          description 
            "The state of system clock. The definition of each 
            possible value is:
            synchronized(0): Indicates local clock is synchronized.
            unsynchronized(1): Indicates local clock is not 
            synchronized.";
        }
        leaf clock-stratum {
          type ntp-stratum;
          mandatory true;
          description
            "The NTP entity's own stratum value. Should be a stratum 
            of syspeer + 1 (or 16 if no syspeer).";
          reference 
            "RFC 5905: Network Time Protocol Version 4: Protocol and 
            Algorithms Specification";  
        }
        leaf clock-refid {
          type union {
            type inet:ipv4-address;
            type binary {
              length "4";
            }
            type string {
              length "4";
            }
          }
          mandatory true;
          description
            "IPv4 address or first 32 bits of the MD5 hash of
            the IPv6 address or reference clock of the peer to
            which clock is synchronized.";
          reference 
            "RFC 5905: Network Time Protocol Version 4: Protocol and 
            Algorithms Specification";  
        }

        uses association-ref {
          description
            "Reference to Association.";
        }

        leaf nominal-freq {
          type decimal64 {
            fraction-digits 4;
          }
          units Hz;
          mandatory true;
          description
            "The nominal frequency of the
            local clock.";
          reference 
            "RFC 5905: Network Time Protocol Version 4: Protocol and 
            Algorithms Specification";  
        }
        leaf actual-freq {
          type decimal64 {
            fraction-digits 4;
          }
          units Hz;
          mandatory true;
          description
            "The actual frequency of the
            local clock.";
          reference 
            "RFC 5905: Network Time Protocol Version 4: Protocol and 
            Algorithms Specification";  
        }
        leaf clock-precision {
          type uint8;
          units Hz;
          mandatory true;
          description
            "Clock precision of this system in integer format 
            (prec=2^(-n)). A value of 5 would mean 2^-5 = 31.25 ms.";
          reference 
            "RFC 5905: Network Time Protocol Version 4: Protocol and 
            Algorithms Specification";  
        }
        leaf clock-offset {
          type decimal64 {
            fraction-digits 3;
          }
          units milliseconds;
          description
            "The time offset to the current selected reference time 
            source e.g., '0.032' or '1.232'.";
          reference 
            "RFC 5905: Network Time Protocol Version 4: Protocol and 
            Algorithms Specification";  
        }
        leaf root-delay {
          type decimal64 {
            fraction-digits 3;
          }
          units milliseconds;
          description
            "Total delay along the path to root clock.";
          reference 
            "RFC 5905: Network Time Protocol Version 4: Protocol and 
            Algorithms Specification";  
        }
        leaf root-dispersion {
          type decimal64 {
            fraction-digits 3;
          }
          units milliseconds;
          description
            "The dispersion between the local clock
            and the root clock, e.g., '6.927'.";
          reference 
            "RFC 5905: Network Time Protocol Version 4: Protocol and 
            Algorithms Specification";  
        }
        leaf reference-time {
          type yang:date-and-time;
          description
            "The reference timestamp.";
        }
        leaf sync-state {
          type ntp-sync-state;
          mandatory true;
          description
            "The synchronization status of
            the local clock.";
        }
      }
    }
    list unicast-configuration {
      key "address type";
      description
        "List of NTP unicast-configurations.";
      leaf address {
        type inet:host;
        description
          "Address of this association.";
      }
      leaf type {
        type unicast-configuration-type;
        description
          "Use client association mode.  This device
          will not provide synchronization to the
          configured NTP server.";
      }
      container authentication{
        description
          "Authentication used for this association.";
        uses authentication;
      }
      leaf prefer {
        type boolean;
        default "false";
        description
          "Whether this association is preferred or not.";
      }
      leaf burst {
        type boolean;
        default "false";
        description
          "If set, a series of packets are sent instead of a single
          packet within each synchronization interval to achieve 
          faster synchronization.";
        reference 
          "RFC 5905: Network Time Protocol Version 4: Protocol and 
          Algorithms Specification";  
      }
      leaf iburst {
        type boolean;
        default "false";
        description
          "If set, a series of packets are sent instead of a single 
          packet within the initial synchronization interval to 
          achieve faster initial synchronization.";
        reference 
          "RFC 5905: Network Time Protocol Version 4: Protocol and 
          Algorithms Specification";  
      }
      leaf source {
        type if:interface-ref;
        description
          "The interface whose IP address is used by this association
          as the source address.";
      }
      uses common-attributes {
        description
          "Common attributes like port, version, min and max
          poll.";
      }
    }
    list associations {
      key "address local-mode isconfigured";
      config "false";
      description
        "List of NTP associations. Here address, local-mode
        and isconfigured is required to uniquely identify
        a particular association. Lets take following examples - 

        1) If RT1 acting as broadcast server,
        and RT2 acting as broadcast client, then RT2
        will form dynamic association with address as RT1,
        local-mode as client and isconfigured as false.

        2) When RT2 is configured
        with unicast-server RT1, then RT2 will form
        association with address as RT1, local-mode as client
        and isconfigured as true. 

        Thus all 3 leaves are needed as key to unique identify
        the association.";
      leaf address {
        type inet:host;
        description
          "The address of this association. Represents the IP
          address of a unicast/multicast/broadcast address.";
      }
      leaf local-mode {
        type association-mode;
        description
          "Local mode of this NTP association.";
      }
      leaf isconfigured {
        type boolean;
        description
          "Indicates if this association is configured or
          dynamically learned.";
      }
      leaf stratum {
        type ntp-stratum;
        description
          "The association stratum value.";
        reference 
          "RFC 5905: Network Time Protocol Version 4: Protocol and 
          Algorithms Specification";  
      }
      leaf refid {
        type union {
          type inet:ipv4-address;
          type binary {
            length "4";
          }
          type string {
            length "4";
          }
        }
        description
          "The refclock driver ID, if available.
          -- a refclock driver ID like '127.127.1.0' for local clock 
             sync
          -- uni/multi/broadcast associations will look like 
             '20.1.1.1'
          -- sync with primary source will look like 'DCN', 'NIST', 
             'ATOM'";
        reference 
          "RFC 5905: Network Time Protocol Version 4: Protocol and 
          Algorithms Specification";  
      }
      leaf authentication{
        type leafref {
          path "/ntp:ntp/ntp:authentication/"
          + "ntp:authentication-keys/ntp:key-id";
        }
        description
          "Authentication Key used for this association.";
      }
      leaf prefer {
        type boolean;
        default "false";
        description
          "Indicates if this association is preferred.";
      }
      leaf peer-interface {
        type if:interface-ref;
        description
          "The interface which is used for communication.";
      }
      uses common-attributes {
        description
          "Common attributes like port, version, min and
          max poll.";
      }
      leaf reach {
        type uint8;
        description
          "The reachability of the configured
          server or peer.";
        reference 
          "RFC 5905: Network Time Protocol Version 4: Protocol and 
          Algorithms Specification";  
      }
      leaf unreach {
        type uint8;
        description
          "The unreachability of the configured
          server or peer.";
        reference 
          "RFC 5905: Network Time Protocol Version 4: Protocol and 
          Algorithms Specification";  
      }
      leaf poll {
        type uint8;
        units seconds;
        description
          "The polling interval for current association";
        reference 
          "RFC 5905: Network Time Protocol Version 4: Protocol and 
          Algorithms Specification";  
      }
      leaf now {
        type uint32;
        units seconds;
        description
          "The time since the NTP packet was
          not received or last synchronized.";
        reference 
          "RFC 5905: Network Time Protocol Version 4: Protocol and 
          Algorithms Specification";  
      }
      leaf offset {
        type decimal64 {
          fraction-digits 3;
        }
        units milliseconds;
        description
          "The offset between the local clock
          and the peer clock, e.g., '0.032' or '1.232'";
        reference 
          "RFC 5905: Network Time Protocol Version 4: Protocol and 
          Algorithms Specification";  
      }
      leaf delay {
        type decimal64 {
          fraction-digits 3;
        }
        units milliseconds;
        description
          "The network delay between the local clock
          and the peer clock.";
        reference 
          "RFC 5905: Network Time Protocol Version 4: Protocol and 
          Algorithms Specification";  
      }
      leaf dispersion {
        type decimal64 {
          fraction-digits 3;
        }
        units milliseconds;
        description
          "The root dispersion between the local clock
           and the peer clock.";
        reference 
          "RFC 5905: Network Time Protocol Version 4: Protocol and 
          Algorithms Specification";  
      }
      leaf originate-time {
        type yang:date-and-time;
        description
          "This is the local time, in timestamp format,
          when latest NTP packet was sent to peer(T1).";
        reference 
          "RFC 5905: Network Time Protocol Version 4: Protocol and 
          Algorithms Specification";  
      }
      leaf receive-time {
        type yang:date-and-time;
        description
          "This is the local time, in timestamp format,
          when latest NTP packet arrived at peer(T2).
          If the peer becomes unreachable the value is set to zero.";
        reference 
          "RFC 5905: Network Time Protocol Version 4: Protocol and 
          Algorithms Specification";  
      }
      leaf transmit-time {
        type yang:date-and-time;
        description
          "This is the local time, in timestamp format,
          at which the NTP packet departed the peer(T3).
          If the peer becomes unreachable the value is set to zero.";
        reference 
          "RFC 5905: Network Time Protocol Version 4: Protocol and 
          Algorithms Specification";  
      }
      leaf input-time {
        type yang:date-and-time;
        description
          "This is the local time, in timestamp format,
          when the latest NTP message from the peer arrived(T4).
          If the peer becomes unreachable the value is set to zero.";
        reference 
          "RFC 5905: Network Time Protocol Version 4: Protocol and 
          Algorithms Specification";  
      }
      container ntp-statistics {
        description
          "Per Peer packet send and receive statistics.";
        uses statistics {
          description
            "NTP send and receive packet statistics.";
        }
      }
    }

    container interfaces {
      description
        "Configuration parameters for NTP interfaces.";
      list interface {
        key "name";
        description
          "List of interfaces.";
        leaf name {
          type if:interface-ref;
          description
            "The interface name.";
        }

        container broadcast-server {
          presence
            "NTP broadcast-server is configured";
          description
            "Configuration of broadcast server.";
          leaf ttl {
            type uint8;
            description
              "Specifies the time to live (TTL) for a
              broadcast packet.";
          }
          container authentication{
            description
              "Authentication used for this association.";
              uses authentication;
          }
          uses common-attributes {
            description
              "Common attribute like port, version, min and
              max poll.";
          }
          reference 
            "RFC 5905: Network Time Protocol Version 4: Protocol and 
            Algorithms Specification";  
        }

        container broadcast-client {
          presence
            "NTP broadcast-client is configured.";
          description
            "Configuration of broadcast-client.";
          reference 
            "RFC 5905: Network Time Protocol Version 4: Protocol and 
            Algorithms Specification";  
        }

        list multicast-server {
          key "address";
          description
            "Configuration of multicast server.";
          leaf address {
            type rt-types:ip-multicast-group-address;
            description
              "The IP address to send NTP multicast packets.";
          }
          leaf ttl {
            type uint8;
            description
              "Specifies the time to live (TTL) for a
              multicast packet.";
          }
          container authentication{
            description
              "Authentication used for this association.";
              uses authentication;
          }
          uses common-attributes {
            description
              "Common attributes like port, version, min and
              max poll.";
          }
          reference 
            "RFC 5905: Network Time Protocol Version 4: Protocol and 
            Algorithms Specification";  
        }
        list multicast-client {
          key "address";
          description
            "Configuration of multicast-client.";
          leaf address {
            type rt-types:ip-multicast-group-address;
            description
              "The IP address of the multicast group to
              join.";
          }
        }
        list manycast-server {
          key "address";
          description
            "Configuration of manycast server.";
          leaf address {
            type rt-types:ip-multicast-group-address;
            description
              "The multicast group IP address to receive
              manycast client messages.";
          }
          reference 
            "RFC 5905: Network Time Protocol Version 4: Protocol and 
            Algorithms Specification";  
        }
        list manycast-client {
          key "address";
          description
            "Configuration of manycast-client.";
          leaf address {
            type rt-types:ip-multicast-group-address;
            description
              "The group IP address that the manycast client
              broadcasts the request message to.";
          }
          container authentication{
            description
              "Authentication used for this association.";
            uses authentication;
          }
          leaf ttl {
            type uint8;
            description
              "Specifies the maximum time to live (TTL) for
              the expanding ring search.";
          }
          leaf minclock {
            type uint8;
            description
              "The minimum manycast survivors in this
              association.";
          }
          leaf maxclock {
            type uint8;
            description
              "The maximum manycast candidates in this
              association.";
          }
          leaf beacon {
            type uint8;
            description
              "The maximum interval between beacons in this
              association.";
          }
          uses common-attributes {
            description
              "Common attributes like port, version, min and
              max poll.";
          }
          reference 
            "RFC 5905: Network Time Protocol Version 4: Protocol and 
            Algorithms Specification";  
        }
      }
    }
    container ntp-statistics {
      config "false";
      description
        "Total NTP packet statistics.";
      uses statistics {
        description
          "NTP send and receive packet statistics.";
      }
    }
  }
}
